;冯大龙编于2020年
(princ "\n数据流一体化开发者：冯大龙、谢雨东、华雷、靳淳、陈杰，版本号V-0.1")
(princ "\n工艺专业：暖通全面通风条件数据提取命令：nsglobal")
(princ "\n工艺专业：做「电气条件」数据提取命令：gselectric")
(princ "\n工艺专业：做「仪表条件」数据提取命令：gsinstrument")
(princ "\n工艺专业：做「外管条件」数据提取命令：gsouterpipe")
(princ "\n工艺专业：做「设备一览表」数据提取命令：gsequipment")
(princ "\n工艺专业：做「管道特性表」数据提取命令：gspipe")
(vl-load-com)

; tansfor gb2312 to utf8
(defun file-encode-trans (file charset1 charset2 / obj encode)
  (setq obj (vlax-create-object "ADODB.Stream"))
  (vlax-put-property obj 'type 2);1????? 2?????
  (vlax-put-property obj 'mode 3);1-?,2-?,3-??
  (vlax-invoke obj 'open)
  (vlax-put-property obj "charset" charset1);;unicode;utf-8;ascii;gb2312;big5;gbk
  (vlax-invoke-method obj 'loadfromfile file)
  (setq encode (vlax-invoke obj 'readtext))
  (vlax-invoke obj 'close)
  (vlax-release-object obj)
  (setq obj (vlax-create-object "ADODB.Stream"))
  (vlax-put-property obj 'type 2);1????? 2?????
  (vlax-put-property obj 'mode 3);1-?,2-?,3-??
  (vlax-invoke obj 'open)
  (vlax-put-property obj "charset" charset2);;unicode;utf-8;ascii;gb2312;big5;gbk
  (vlax-invoke obj 'writetext encode)
  (vlax-invoke-method obj 'savetofile file 2);1??,2??
  (vlax-invoke obj 'flush);???????????
  (vlax-invoke obj 'close)
  (vlax-release-object obj)
)

; get the current file direction
(defun getFileDir (/ fn)
  (print "请输入拟输出的文件名（无需扩展名），输出文件自动存放在 CAD 文件同一个文件夹内")
  (setq fn (getstring "\nfilename: "))
  (setq currentDir (getvar "dwgprefix"))
  (setq fn (strcat currentDir fn ".txt"))
)

; write the proptery of block to txt
(defun writeProperty (value captialName lowerName entx f / proptery)
  (if (= value captialName)
    (progn
      (setq proptery (cdr (assoc 1 entx)))
      (princ (strcat "\"" lowerName "\": \"" proptery "\",") f)
    )
  )
)

;  the command for extarcting data from the for PipeArrow Blocks
(defun c:gspipe (/ fn f ssLeft ssRight ssUp ssDown)
  (setq fn (getFileDir))
  (setq f (open fn "w"))
  (setq ssLeft (ssget "x" '((0 . "INSERT") (2 . "PipeArrowLeft"))))
  (setq ssRight (ssget "x" '((0 . "INSERT") (2 . "PipeArrowRight"))))
  (setq ssUp (ssget "x" '((0 . "INSERT") (2 . "PipeArrowUp"))))
  (setq ssDown (ssget "x" '((0 . "INSERT") (2 . "PipeArrowDown"))))
  (ExtactPipeArrow f ssLeft)
  (ExtactPipeArrow f ssRight)
  (ExtactPipeArrow f ssUp)
  (ExtactPipeArrow f ssDown)
  (close f)
  ; tansfor the encode
  (file-encode-trans fn "gb2312" "utf-8")
  (print "数据提取成功")(princ)
)

; the command for extarcting data from globalVentilation Block
(defun c:nsglobal (/ fn f ssRoom ssSubstance ssHotWet)
  (setq fn (getFileDir))
  (setq f (open fn "w"))
  (setq ssRoom (ssget "x" '((0 . "INSERT") (2 . "RoomData"))))
  (setq ssSubstance (ssget "x" '((0 . "INSERT") (2 . "SubstanceData"))))
  (setq ssHotWet (ssget "x" '((0 . "INSERT") (2 . "HotWetData"))))
  (ExtactGlobalRoom f ssRoom)
  (ExtactGlobalSubstance f ssSubstance)
  (ExtactGlobalHotWet f ssHotWet)
  (close f)
  ; tansfor the encode
  (file-encode-trans fn "gb2312" "utf-8")
  (print "数据提取成功")(princ)
)

; the command for extarcting data from InstrumentP/InstrumentL Block
(defun c:gsinstrument (/ fn f ssP ssL)
  (setq fn (getFileDir))
  (setq f (open fn "w"))
  (setq ssP (ssget "x" '((0 . "INSERT") (2 . "InstrumentP"))))
  (setq ssL (ssget "x" '((0 . "INSERT") (2 . "InstrumentL"))))
  (ExtactInstrumentP f ssP)
  (ExtactInstrumentL f ssL)
  (close f)
  ; tansfor the encode
  (file-encode-trans fn "gb2312" "utf-8")
  (print "数据提取成功")(princ)
)

; the command for extarcting data from Equipment Block
(defun c:gsequipment (/ fn f ssReactor ssPump ssTank ssHeater)
  (setq fn (getFileDir))
  (setq f (open fn "w"))
  (setq ssReactor (ssget "x" '((0 . "INSERT") (2 . "Reactor"))))
  (setq ssPump (ssget "x" '((0 . "INSERT") (2 . "Pump"))))
  (setq ssTank (ssget "x" '((0 . "INSERT") (2 . "Tank"))))
  (setq ssHeater (ssget "x" '((0 . "INSERT") (2 . "Heater"))))
  (ExtactReactor f ssReactor)
  (ExtactPump f ssPump)
  (ExtactTank f ssTank)
  (ExtactHeater f ssHeater)
  (close f)
  ; tansfor the encode
  (file-encode-trans fn "gb2312" "utf-8")
  (print "数据提取成功")(princ)
)

; the command for extarcting data from OuterPipe Block
(defun c:gsouterpipe (/ fn f ssRightTo ssRightFrom ssLeftTo ssLeftFrom)
  (setq fn (getFileDir))
  (setq f (open fn "w"))
  (setq ssRightTo (ssget "x" '((0 . "INSERT") (2 . "OuterPipeRightTo"))))
  (setq ssRightFrom (ssget "x" '((0 . "INSERT") (2 . "OuterPipeRightFrom"))))
  (setq ssLeftTo (ssget "x" '((0 . "INSERT") (2 . "OuterPipeLeftTo"))))
  (setq ssLeftFrom (ssget "x" '((0 . "INSERT") (2 . "OuterPipeLeftFrom"))))
  (ExtactOuterPipe f ssRightTo)
  (ExtactOuterPipe f ssRightFrom)
  (ExtactOuterPipe f ssLeftTo)
  (ExtactOuterPipe f ssLeftFrom)
  (close f)
  ; tansfor the encode
  (file-encode-trans fn "gb2312" "utf-8")
  (print "数据提取成功")(princ)
)

; extarct data form the for OuterPipe Blocks
(defun ExtactOuterPipe (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "DWGNUM" "dwgnum" entx f)
              (writeProperty value "PIPENUM" "pipenum" entx f)
              (writeProperty value "FROM" "from" entx f)
              (writeProperty value "TO" "to" entx f)
              (writeProperty value "SUBSTANCE" "substance" entx f)
              (writeProperty value "TEMP" "temp" entx f)
              (writeProperty value "PRESSURE" "pressure" entx f)
              (writeProperty value "PHASE" "phase" entx f)
              (writeProperty value "DESIGNFLOW" "designflow" entx f)
              (writeProperty value "PRESSURESPEC" "pressurespec" entx f)
              (writeProperty value "OPERATESPEC" "opratespec" entx f)
              (writeProperty value "EARTH" "earth" entx f)
              (writeProperty value "INSULATION" "insulation" entx f)
              (writeProperty value "PROTECTION" "protection" entx f)
              (writeProperty value "WELD" "weld" entx f)
              (writeProperty value "INSULATION" "insulation" entx f)
              (if (= value "FLANGE")
                (progn
                  (setq flange (cdr (assoc 1 entx)))
                  (princ (strcat "\"flange\": \"" flange "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form Reactor Block
(defun ExtactHeater (f ss / N index i ent blk entx value number)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "AREA" "area" entx f)
              (writeProperty value "TEMP" "temp" entx f)
              (writeProperty value "PRESSURE" "pressure" entx f)
              (writeProperty value "MATERIAL" "material" entx f)
              (writeProperty value "WEIGHT" "weight" entx f)
              (if (= value "NUMBER")
                (progn
                  (setq number (cdr (assoc 1 entx)))
                  (princ (strcat "\"class\": \"" "heater" "\",") f)
                  (princ (strcat "\"number\": \"" number "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form Reactor Block
(defun ExtactTank (f ss / N index i ent blk entx value expressure)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "VOLUME" "volumn" entx f)
              (writeProperty value "TEMP" "temp" entx f)
              (writeProperty value "PRESSURE" "pressure" entx f)
              (writeProperty value "MATERIAL" "material" entx f)
              (writeProperty value "WEIGHT" "weight" entx f)
              (writeProperty value "NUMBER" "number" entx f)
              (writeProperty value "EXTEMP" "extemp" entx f)
              (if (= value "EXPRESSURE")
                (progn
                  (setq expressure (cdr (assoc 1 entx)))
                  (princ (strcat "\"class\": \"" "tank" "\",") f)
                  (princ (strcat "\"expressure\": \"" expressure "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form Reactor Block
(defun ExtactPump (f ss / N index i ent blk entx value equiptype)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "FLOW" "flow" entx f)
              (writeProperty value "HEAD" "head" entx f)
              (writeProperty value "POWER" "power" entx f)
              (writeProperty value "MATERIAL" "material" entx f)
              (writeProperty value "WEIGHT" "weight" entx f)
              (writeProperty value "NUMBER" "number" entx f)
              (if (= value "TYPE")
                (progn
                  (setq equiptype (cdr (assoc 1 entx)))
                  (princ (strcat "\"class\": \"" "pump" "\",") f)
                  (princ (strcat "\"type\": \"" equiptype "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form Reactor Block
(defun ExtactReactor (f ss / N index i ent blk entx value expressure)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "VOLUME" "volumn" entx f)
              (writeProperty value "POWER" "power" entx f)
              (writeProperty value "TEMP" "temp" entx f)
              (writeProperty value "PRESSURE" "pressure" entx f)
              (writeProperty value "MATERIAL" "material" entx f)
              (writeProperty value "WEIGHT" "weight" entx f)
              (writeProperty value "NUMBER" "number" entx f)
              (writeProperty value "TYPE" "type" entx f)
              (writeProperty value "EXTEMP" "extemp" entx f)
              (if (= value "EXPRESSURE")
                (progn
                  (setq expressure (cdr (assoc 1 entx)))
                  (princ (strcat "\"class\": \"" "reactor" "\",") f)
                  (princ (strcat "\"expressure\": \"" expressure "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form InstrumentL Block
(defun ExtactInstrumentL (f ss / N index i ent blk entx value nomal)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "FUNCTION" "function" entx f)
              (writeProperty value "SUBSTANCE" "substance" entx f)
              (writeProperty value "TEMP" "temp" entx f)
              (writeProperty value "PRESSURE" "pressure" entx f)
              (writeProperty value "PHASE" "phase" entx f)
              (writeProperty value "MATERIAL" "material" entx f)
              (writeProperty value "NAME" "name" entx f)
              (writeProperty value "LOCATION" "location" entx f)
              (writeProperty value "MIN" "minvalue" entx f)
              (writeProperty value "MAX" "maxvalue" entx f)
	      (writeProperty value "NOMAL" "nomal" entx f)
	      (writeProperty value "INSTALLSIZE" "installsize" entx f)
              (if (= value "DIRECTION")
                (progn
                  (setq direction (cdr (assoc 1 entx)))
                  (princ (strcat "\"class\": \"" "location" "\",") f)
                  (princ (strcat "\"direction\": \"" direction "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form InstrumentP Block
(defun ExtactInstrumentP (f ss / N index i ent blk entx value nomal)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "FUNCTION" "function" entx f)
              (writeProperty value "HALARM" "halarm" entx f)
              (writeProperty value "LALARM" "lalarm" entx f)
              (writeProperty value "SUBSTANCE" "substance" entx f)
              (writeProperty value "TEMP" "temp" entx f)
              (writeProperty value "PRESSURE" "pressure" entx f)
              (writeProperty value "PHASE" "phase" entx f)
              (writeProperty value "MATERIAL" "material" entx f)
              (writeProperty value "NAME" "name" entx f)
              (writeProperty value "LOCATION" "location" entx f)
              (writeProperty value "MIN" "minvalue" entx f)
              (writeProperty value "MAX" "maxvalue" entx f)
	      (writeProperty value "NOMAL" "nomal" entx f)
	      (writeProperty value "INSTALLSIZE" "installsize" entx f)
              (if (= value "DIRECTION")
                (progn
                  (setq direction (cdr (assoc 1 entx)))
                  (princ (strcat "\"class\": \"" "concentrated" "\",") f)
                  (princ (strcat "\"direction\": \"" direction "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form HotWetData Block
(defun ExtactGlobalHotWet (f ss / N index i ent blk entx value water_temp)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "ROOM_NUM" "room_num" entx f)
              (writeProperty value "EQUIPMENT_NUM" "equipment_num" entx f)
              (writeProperty value "TYPE" "type" entx f)
              (writeProperty value "AIR_EXHAUST" "air_exhaust" entx f)
              (writeProperty value "PRESERVE_HEAT" "preserve_heat" entx f)
              (writeProperty value "POWER" "power" entx f)
              (writeProperty value "SURFACE_AREA" "surface_area" entx f)
              (writeProperty value "SURFACE_TEMP" "surface_temp" entx f)
              (writeProperty value "WATER_AREA" "water_area" entx f)
              (if (= value "WATER_TEMP")
                (progn
                  (setq water_temp (cdr (assoc 1 entx)))
                  (princ (strcat "\"block_data\": \"" "hotwet" "\",") f)
                  (princ (strcat "\"water_temp\": \"" water_temp "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form SubstanceData Block
(defun ExtactGlobalSubstance (f ss / N index i ent blk entx value compress_num)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "ROOM_NUM" "room_num" entx f)
              (writeProperty value "SUBSTANCE_NAME" "substance_name" entx f)
              (writeProperty value "VALUE_NUM" "value_num" entx f)
              (writeProperty value "PUMPSEAL_NUM" "pumpseal_num" entx f)
              (writeProperty value "FLANGE_NUM" "flange_num" entx f)
              (writeProperty value "DISCHARGE_NUM" "discharge_num" entx f)
              (writeProperty value "SAFETY_NUM" "safety_num" entx f)
              (if (= value "COMPRESS_NUM")
                (progn
                  (setq compress_num (cdr (assoc 1 entx)))
                  (princ (strcat "\"block_data\": \"" "substance" "\",") f)
                  (princ (strcat "\"compress_num\": \"" compress_num "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form RoomData Block
(defun ExtactGlobalRoom (f ss / N index i ent blk entx value winter_rehumidity)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "ROOM_NUM" "room_num" entx f)
              (writeProperty value "ROOM_NAME" "room_name" entx f)
              (writeProperty value "ROOM_AREA" "room_area" entx f)
              (writeProperty value "ROOM_HEIGHT" "room_height" entx f)
              (writeProperty value "ROOM_PRESSURE" "room_pressure" entx f)
              (writeProperty value "SUMMER_TEMP" "summer_temp" entx f)
              (writeProperty value "SUMMER_REHUMIDITY" "summer_rehumidity" entx f)
              (writeProperty value "WINTER_TEMP" "winter_temp" entx f)
              (if (= value "WINTER_REHUMIDITY")
                (progn
                  (setq winter_rehumidity (cdr (assoc 1 entx)))
                  (princ (strcat "\"block_data\": \"" "room" "\",") f)
                  (princ (strcat "\"winter_rehumidity\": \"" winter_rehumidity "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form the for PipeArrow Blocks
(defun ExtactPipeArrow (f ss / N index i ent blk entx value pipenum substance temp pressure phase fromP toP insulation)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "PIPENUM" "pipenum" entx f)
              (writeProperty value "SUBSTANCE" "substance" entx f)
              (writeProperty value "TEMP" "temp" entx f)
              (writeProperty value "PRESSURE" "pressure" entx f)
              (writeProperty value "PHASE" "phase" entx f)
              (writeProperty value "FROM" "from" entx f)
              (writeProperty value "TO" "to" entx f)
              (if (= value "INSULATION")
                (progn
                  (setq insulation (cdr (assoc 1 entx)))
                  (princ (strcat "\"insulation\": \"" insulation "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)
