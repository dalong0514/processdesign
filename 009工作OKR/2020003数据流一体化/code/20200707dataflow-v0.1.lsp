;冯大龙编于2020年
(princ "\n数据流一体化开发者：冯大龙、谢雨东、华雷、靳淳、陈杰")
(princ "\n工艺专业：暖通全面通风条件数据提取命令：nsglobal")
(princ "\n工艺专业：做「电气条件」数据提取命令：gselectric")
(princ "\n工艺专业：做「仪表条件」数据提取命令：gsinstrument")
(princ "\n工艺专业：做「外管条件」数据提取命令：gsouterpipe")
(princ "\n工艺专业：做「设备一览表」数据提取命令：gsequipment")
(princ "\n工艺专业：做「管道特性表」数据提取命令：gspipe")
(vl-load-com)

; tansfor gb2312 to utf8
(defun file-encode-trans (file charset1 charset2 / obj encode)
  (setq obj (vlax-create-object "ADODB.Stream"))
  (vlax-put-property obj 'type 2);1????? 2?????
  (vlax-put-property obj 'mode 3);1-?,2-?,3-??
  (vlax-invoke obj 'open)
  (vlax-put-property obj "charset" charset1);;unicode;utf-8;ascii;gb2312;big5;gbk
  (vlax-invoke-method obj 'loadfromfile file)
  (setq encode (vlax-invoke obj 'readtext))
  (vlax-invoke obj 'close)
  (vlax-release-object obj)
  (setq obj (vlax-create-object "ADODB.Stream"))
  (vlax-put-property obj 'type 2);1????? 2?????
  (vlax-put-property obj 'mode 3);1-?,2-?,3-??
  (vlax-invoke obj 'open)
  (vlax-put-property obj "charset" charset2);;unicode;utf-8;ascii;gb2312;big5;gbk
  (vlax-invoke obj 'writetext encode)
  (vlax-invoke-method obj 'savetofile file 2);1??,2??
  (vlax-invoke obj 'flush);???????????
  (vlax-invoke obj 'close)
  (vlax-release-object obj)
)

; get the current file direction
(defun getFileDir (/ fn)
  (print "请输入拟输出的文件名（无需扩展名），输出文件自动存放在 CAD 文件同一个文件夹内")
  (setq fn (getstring "\nfilename: "))
  (setq currentDir (getvar "dwgprefix"))
  (setq fn (strcat currentDir fn ".txt"))
)

; write the proptery of block to txt
(defun writeProperty (value captialName ent f / name)
  (if (= value captialName)
    (progn
      (setq name (cdr (assoc 1 entx)))
      (princ (strcat "\"" name "\": \"" name "\",") f)
    )
  )
)

;  the command for extarcting data from the for PipeArrow Blocks
(defun c:gspipe (/ fn f ssLeft ssRight ssUp ssDown)
  (setq fn (getFileDir))
  (setq f (open fn "w"))
  (setq ssLeft (ssget "x" '((0 . "INSERT") (2 . "PipeArrowLeft"))))
  (setq ssRight (ssget "x" '((0 . "INSERT") (2 . "PipeArrowRight"))))
  (setq ssUp (ssget "x" '((0 . "INSERT") (2 . "PipeArrowUp"))))
  (setq ssDown (ssget "x" '((0 . "INSERT") (2 . "PipeArrowDown"))))
  (ExtactPipeArrow f ssLeft)
  (ExtactPipeArrow f ssRight)
  (ExtactPipeArrow f ssUp)
  (ExtactPipeArrow f ssDown)
  (close f)
  ; tansfor the encode
  (file-encode-trans fn "gb2312" "utf-8")
  (print "数据提取成功")(princ)
)

; the command for extarcting data from globalVentilation Block
(defun c:nsglobal (/ fn f ssRoom ssSubstance ssHotWet)
  (setq fn (getFileDir))
  (setq f (open fn "w"))
  (setq ssRoom (ssget "x" '((0 . "INSERT") (2 . "RoomData"))))
  (setq ssSubstance (ssget "x" '((0 . "INSERT") (2 . "SubstanceData"))))
  (setq ssHotWet (ssget "x" '((0 . "INSERT") (2 . "HotWetData"))))
  (ExtactGlobalRoom f ssRoom)
  (ExtactGlobalSubstance f ssSubstance)
  (ExtactGlobalHotWet f ssHotWet)
  (close f)
  ; tansfor the encode
  (file-encode-trans fn "gb2312" "utf-8")
  (print "数据提取成功")(princ)
)

; the command for extarcting data from InstrumentP/InstrumentL Block
(defun c:gsinstrument (/ fn f ssP ssL)
  (setq fn (getFileDir))
  (setq f (open fn "w"))
  (setq ssP (ssget "x" '((0 . "INSERT") (2 . "InstrumentP"))))
  (setq ssL (ssget "x" '((0 . "INSERT") (2 . "InstrumentL"))))
  (ExtactInstrumentP f ssP)
  (ExtactInstrumentL f ssL)
  (close f)
  ; tansfor the encode
  (file-encode-trans fn "gb2312" "utf-8")
  (print "数据提取成功")(princ)
)

; the command for extarcting data from Equipment Block
(defun c:gsequipment (/ fn f ssReactor ssPump ssTank ssHeater)
  (setq fn (getFileDir))
  (setq f (open fn "w"))
  (setq ssReactor (ssget "x" '((0 . "INSERT") (2 . "Reactor"))))
  (setq ssPump (ssget "x" '((0 . "INSERT") (2 . "Pump"))))
  (setq ssTank (ssget "x" '((0 . "INSERT") (2 . "Tank"))))
  (setq ssHeater (ssget "x" '((0 . "INSERT") (2 . "Heater"))))
  (ExtactReactor f ssReactor)
  (ExtactPump f ssPump)
  (ExtactTank f ssTank)
  (ExtactHeater f ssHeater)
  (close f)
  ; tansfor the encode
  (file-encode-trans fn "gb2312" "utf-8")
  (print "数据提取成功")(princ)
)

; the command for extarcting data from OuterPipe Block
(defun c:gsouterpipe (/ fn f ssRightTo ssRightFrom ssLeftTo ssLeftFrom)
  (setq fn (getFileDir))
  (setq f (open fn "w"))
  (setq ssRightTo (ssget "x" '((0 . "INSERT") (2 . "OuterPipeRightTo"))))
  (setq ssRightFrom (ssget "x" '((0 . "INSERT") (2 . "OuterPipeRightFrom"))))
  (setq ssLeftTo (ssget "x" '((0 . "INSERT") (2 . "OuterPipeLeftTo"))))
  (setq ssLeftFrom (ssget "x" '((0 . "INSERT") (2 . "OuterPipeLeftFrom"))))
  (ExtactOuterPipe f ssRightTo)
  (ExtactOuterPipe f ssRightFrom)
  (ExtactOuterPipe f ssLeftTo)
  (ExtactOuterPipe f ssLeftFrom)
  (close f)
  ; tansfor the encode
  (file-encode-trans fn "gb2312" "utf-8")
  (print "数据提取成功")(princ)
)

; extarct data form the for OuterPipe Blocks
(defun ExtactOuterPipe (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "DWGNUM")
                (progn
                  (setq dwgnum (cdr (assoc 1 entx)))
                  (princ (strcat "\"dwgnum\": \"" dwgnum "\",") f)
                )
              )
              (if (= value "PIPENUM")
                (progn
                  (setq pipenum (cdr (assoc 1 entx)))
                  (princ (strcat "\"pipenum\": \"" pipenum "\",") f)
                )
              )
              (if (= value "FROM")
                (progn
                  (setq fromP (cdr (assoc 1 entx)))
                  (princ (strcat "\"from\": \"" fromP "\",") f)
                )
              )
              (if (= value "TO")
                (progn
                  (setq toP (cdr (assoc 1 entx)))
                  (princ (strcat "\"to\": \"" toP "\",") f)
                )
              )
              (if (= value "SUBSTANCE")
                (progn
                  (setq substance (cdr (assoc 1 entx)))
                  (princ (strcat "\"substance\": \"" substance "\",") f)
                )
              )
              (if (= value "TEMP")
                (progn
                  (setq temp (cdr (assoc 1 entx)))
                  (princ (strcat "\"temp\": \"" temp "\",") f)
                )
              )
              (if (= value "PRESSURE")
                (progn
                  (setq pressure (cdr (assoc 1 entx)))
                  (princ (strcat "\"pressure\": \"" pressure "\",") f)
                )
              )
              (if (= value "PHASE")
                (progn
                  (setq phase (cdr (assoc 1 entx)))
                  (princ (strcat "\"phase\": \"" phase "\",") f)
                )
              )
              (if (= value "DESIGNFLOW")
                (progn
                  (setq designflow (cdr (assoc 1 entx)))
                  (princ (strcat "\"designflow\": \"" designflow "\",") f)
                )
              )
              (if (= value "DESIGNVELOCITY")
                (progn
                  (setq designvelocity (cdr (assoc 1 entx)))
                  (princ (strcat "\"designvelocity\": \"" designvelocity "\",") f)
                )
              )
              (if (= value "PRESSURESPEC")
                (progn
                  (setq pressurespec (cdr (assoc 1 entx)))
                  (princ (strcat "\"pressurespec\": \"" pressurespec "\",") f)
                )
              )
              (if (= value "OPERATESPEC")
                (progn
                  (setq opratespec (cdr (assoc 1 entx)))
                  (princ (strcat "\"opratespec\": \"" opratespec "\",") f)
                )
              )
              (if (= value "EARTH")
                (progn
                  (setq earth (cdr (assoc 1 entx)))
                  (princ (strcat "\"earth\": \"" earth "\",") f)
                )
              )
              (if (= value "INSULATION")
                (progn
                  (setq insulation (cdr (assoc 1 entx)))
                  (princ (strcat "\"insulation\": \"" insulation "\",") f)
                )
              )
              (if (= value "PROTECTION")
                (progn
                  (setq protection (cdr (assoc 1 entx)))
                  (princ (strcat "\"protection\": \"" protection "\",") f)
                )
              )
              (if (= value "WELD")
                (progn
                  (setq weld (cdr (assoc 1 entx)))
                  (princ (strcat "\"weld\": \"" weld "\",") f)
                )
              )
              (if (= value "FLANGE")
                (progn
                  (setq flange (cdr (assoc 1 entx)))
                  (princ (strcat "\"flange\": \"" flange "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form Reactor Block
(defun ExtactHeater (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "TAG")
                (progn
                  (setq tag (cdr (assoc 1 entx)))
                  (princ (strcat "\"tag\": \"" tag "\",") f)
                  (princ (strcat "\"class\": \"" "heater" "\",") f)
                )
              )
              (if (= value "NAME")
                (progn
                  (setq name (cdr (assoc 1 entx)))
                  (princ (strcat "\"name\": \"" name "\",") f)
                )
              )
              (if (= value "AREA")
                (progn
                  (setq area (cdr (assoc 1 entx)))
                  (princ (strcat "\"area\": \"" area "\",") f)
                )
              )
              (if (= value "TEMP")
                (progn
                  (setq temp (cdr (assoc 1 entx)))
                  (princ (strcat "\"temp\": \"" temp "\",") f)
                )
              )
              (if (= value "PRESSURE")
                (progn
                  (setq pressure (cdr (assoc 1 entx)))
                  (princ (strcat "\"pressure\": \"" pressure "\",") f)
                )
              )
              (if (= value "MATERIAL")
                (progn
                  (setq material (cdr (assoc 1 entx)))
                  (princ (strcat "\"material\": \"" material "\",") f)
                )
              )
              (if (= value "WEIGHT")
                (progn
                  (setq weight (cdr (assoc 1 entx)))
                  (princ (strcat "\"weight\": \"" weight "\",") f)
                )
              )
              (if (= value "NUMBER")
                (progn
                  (setq number (cdr (assoc 1 entx)))
                  (princ (strcat "\"number\": \"" number "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form Reactor Block
(defun ExtactTank (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "TAG")
                (progn
                  (setq tag (cdr (assoc 1 entx)))
                  (princ (strcat "\"tag\": \"" tag "\",") f)
                  (princ (strcat "\"class\": \"" "tank" "\",") f)
                )
              )
              (if (= value "NAME")
                (progn
                  (setq name (cdr (assoc 1 entx)))
                  (princ (strcat "\"name\": \"" name "\",") f)
                )
              )
              (if (= value "VOLUMN")
                (progn
                  (setq volumn (cdr (assoc 1 entx)))
                  (princ (strcat "\"volumn\": \"" volumn "\",") f)
                )
              )
              (if (= value "TEMP")
                (progn
                  (setq temp (cdr (assoc 1 entx)))
                  (princ (strcat "\"temp\": \"" temp "\",") f)
                )
              )
              (if (= value "PRESSURE")
                (progn
                  (setq pressure (cdr (assoc 1 entx)))
                  (princ (strcat "\"pressure\": \"" pressure "\",") f)
                )
              )
              (if (= value "MATERIAL")
                (progn
                  (setq material (cdr (assoc 1 entx)))
                  (princ (strcat "\"material\": \"" material "\",") f)
                )
              )
              (if (= value "WEIGHT")
                (progn
                  (setq weight (cdr (assoc 1 entx)))
                  (princ (strcat "\"weight\": \"" weight "\",") f)
                )
              )
              (if (= value "NUMBER")
                (progn
                  (setq number (cdr (assoc 1 entx)))
                  (princ (strcat "\"number\": \"" number "\",") f)
                )
              )
              (if (= value "EXTEMP")
                (progn
                  (setq extemp (cdr (assoc 1 entx)))
                  (princ (strcat "\"extemp\": \"" maxValue "\",") f)
                )
              )
              (if (= value "EXPRESSURE")
                (progn
                  (setq expressure (cdr (assoc 1 entx)))
                  (princ (strcat "\"expressure\": \"" expressure "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form Reactor Block
(defun ExtactPump (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "TAG")
                (progn
                  (setq tag (cdr (assoc 1 entx)))
                  (princ (strcat "\"tag\": \"" tag "\",") f)
                  (princ (strcat "\"class\": \"" "pump" "\",") f)
                )
              )
              (if (= value "NAME")
                (progn
                  (setq name (cdr (assoc 1 entx)))
                  (princ (strcat "\"name\": \"" name "\",") f)
                )
              )
              (if (= value "FLOW")
                (progn
                  (setq flow (cdr (assoc 1 entx)))
                  (princ (strcat "\"flow\": \"" flow "\",") f)
                )
              )
              (if (= value "HEAD")
                (progn
                  (setq head (cdr (assoc 1 entx)))
                  (princ (strcat "\"head\": \"" head "\",") f)
                )
              )
              (if (= value "POWER")
                (progn
                  (setq power (cdr (assoc 1 entx)))
                  (princ (strcat "\"power\": \"" power "\",") f)
                )
              )
              (if (= value "MATERIAL")
                (progn
                  (setq material (cdr (assoc 1 entx)))
                  (princ (strcat "\"material\": \"" material "\",") f)
                )
              )
              (if (= value "WEIGHT")
                (progn
                  (setq weight (cdr (assoc 1 entx)))
                  (princ (strcat "\"weight\": \"" weight "\",") f)
                )
              )
              (if (= value "NUMBER")
                (progn
                  (setq number (cdr (assoc 1 entx)))
                  (princ (strcat "\"number\": \"" number "\",") f)
                )
              )
              (if (= value "TYPE")
                (progn
                  (setq equiptype (cdr (assoc 1 entx)))
                  (princ (strcat "\"type\": \"" equiptype "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form Reactor Block
(defun ExtactReactor (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "TAG")
                (progn
                  (setq tag (cdr (assoc 1 entx)))
                  (princ (strcat "\"tag\": \"" tag "\",") f)
                  (princ (strcat "\"class\": \"" "reactor" "\",") f)
                )
              )
              (if (= value "NAME")
                (progn
                  (setq name (cdr (assoc 1 entx)))
                  (princ (strcat "\"name\": \"" name "\",") f)
                )
              )
              (if (= value "VOLUMN")
                (progn
                  (setq volumn (cdr (assoc 1 entx)))
                  (princ (strcat "\"volumn\": \"" volumn "\",") f)
                )
              )
              (if (= value "POWER")
                (progn
                  (setq power (cdr (assoc 1 entx)))
                  (princ (strcat "\"power\": \"" power "\",") f)
                )
              )
              (if (= value "TEMP")
                (progn
                  (setq temp (cdr (assoc 1 entx)))
                  (princ (strcat "\"temp\": \"" temp "\",") f)
                )
              )
              (if (= value "PRESSURE")
                (progn
                  (setq pressure (cdr (assoc 1 entx)))
                  (princ (strcat "\"pressure\": \"" pressure "\",") f)
                )
              )
              (if (= value "MATERIAL")
                (progn
                  (setq material (cdr (assoc 1 entx)))
                  (princ (strcat "\"material\": \"" material "\",") f)
                )
              )
              (if (= value "WEIGHT")
                (progn
                  (setq weight (cdr (assoc 1 entx)))
                  (princ (strcat "\"weight\": \"" weight "\",") f)
                )
              )
              (if (= value "NUMBER")
                (progn
                  (setq number (cdr (assoc 1 entx)))
                  (princ (strcat "\"number\": \"" number "\",") f)
                )
              )
              (if (= value "TYPE")
                (progn
                  (setq equiptype (cdr (assoc 1 entx)))
                  (princ (strcat "\"type\": \"" equiptype "\",") f)
                )
              )
              (if (= value "EXTEMP")
                (progn
                  (setq extemp (cdr (assoc 1 entx)))
                  (princ (strcat "\"extemp\": \"" maxValue "\",") f)
                )
              )
              (if (= value "EXPRESSURE")
                (progn
                  (setq expressure (cdr (assoc 1 entx)))
                  (princ (strcat "\"expressure\": \"" expressure "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form InstrumentL Block
(defun ExtactInstrumentL (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "TAG")
                (progn
                  (setq tag (cdr (assoc 1 entx)))
                  (princ (strcat "\"tag\": \"" tag "\",") f)
                  (princ (strcat "\"type\": \"" "location" "\",") f)
                )
              )
              (if (= value "FUNCTION")
                (progn
                  (setq functon (cdr (assoc 1 entx)))
                  (princ (strcat "\"functon\": \"" functon "\",") f)
                )
              )
              (if (= value "SUBSTANCE")
                (progn
                  (setq substance (cdr (assoc 1 entx)))
                  (princ (strcat "\"substance\": \"" substance "\",") f)
                )
              )
              (if (= value "TEMP")
                (progn
                  (setq temp (cdr (assoc 1 entx)))
                  (princ (strcat "\"temp\": \"" temp "\",") f)
                )
              )
              (if (= value "PRESSURE")
                (progn
                  (setq pressure (cdr (assoc 1 entx)))
                  (princ (strcat "\"pressure\": \"" pressure "\",") f)
                )
              )
              (if (= value "MATERIAL")
                (progn
                  (setq material (cdr (assoc 1 entx)))
                  (princ (strcat "\"material\": \"" material "\",") f)
                )
              )
              (if (= value "NAME")
                (progn
                  (setq name (cdr (assoc 1 entx)))
                  (princ (strcat "\"name\": \"" name "\",") f)
                )
              )
              (if (= value "LOCATION")
                (progn
                  (setq location (cdr (assoc 1 entx)))
                  (princ (strcat "\"location\": \"" location "\",") f)
                )
              )
              (if (= value "MIN")
                (progn
                  (setq minvalue (cdr (assoc 1 entx)))
                  (princ (strcat "\"minvalue\": \"" minvalue "\",") f)
                )
              )
              (if (= value "MAX")
                (progn
                  (setq maxValue (cdr (assoc 1 entx)))
                  (princ (strcat "\"maxValue\": \"" maxValue "\",") f)
                )
              )
              (if (= value "NOMAL")
                (progn
                  (setq nomal (cdr (assoc 1 entx)))
                  (princ (strcat "\"nomal\": \"" nomal "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form InstrumentP Block
(defun ExtactInstrumentP (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "TAG")
                (progn
                  (setq tag (cdr (assoc 1 entx)))
                  (princ (strcat "\"tag\": \"" tag "\",") f)
                  (princ (strcat "\"type\": \"" "concentrated" "\",") f)
                )
              )
              (if (= value "FUNCTION")
                (progn
                  (setq functon (cdr (assoc 1 entx)))
                  (princ (strcat "\"functon\": \"" functon "\",") f)
                )
              )
              (if (= value "HALARM")
                (progn
                  (setq halarm (cdr (assoc 1 entx)))
                  (princ (strcat "\"halarm\": \"" halarm "\",") f)
                )
              )
              (if (= value "LALARM")
                (progn
                  (setq lalarm (cdr (assoc 1 entx)))
                  (princ (strcat "\"lalarm\": \"" lalarm "\",") f)
                )
              )
              (if (= value "SUBSTANCE")
                (progn
                  (setq substance (cdr (assoc 1 entx)))
                  (princ (strcat "\"substance\": \"" substance "\",") f)
                )
              )
              (if (= value "TEMP")
                (progn
                  (setq temp (cdr (assoc 1 entx)))
                  (princ (strcat "\"temp\": \"" temp "\",") f)
                )
              )
              (if (= value "PRESSURE")
                (progn
                  (setq pressure (cdr (assoc 1 entx)))
                  (princ (strcat "\"pressure\": \"" pressure "\",") f)
                )
              )
              (if (= value "MATERIAL")
                (progn
                  (setq material (cdr (assoc 1 entx)))
                  (princ (strcat "\"material\": \"" material "\",") f)
                )
              )
              (if (= value "NAME")
                (progn
                  (setq name (cdr (assoc 1 entx)))
                  (princ (strcat "\"name\": \"" name "\",") f)
                )
              )
              (if (= value "LOCATION")
                (progn
                  (setq location (cdr (assoc 1 entx)))
                  (princ (strcat "\"location\": \"" location "\",") f)
                )
              )
              (if (= value "MIN")
                (progn
                  (setq minvalue (cdr (assoc 1 entx)))
                  (princ (strcat "\"minvalue\": \"" minvalue "\",") f)
                )
              )
              (if (= value "MAX")
                (progn
                  (setq maxValue (cdr (assoc 1 entx)))
                  (princ (strcat "\"maxValue\": \"" maxValue "\",") f)
                )
              )
              (if (= value "NOMAL")
                (progn
                  (setq nomal (cdr (assoc 1 entx)))
                  (princ (strcat "\"nomal\": \"" nomal "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form HotWetData Block
(defun ExtactGlobalHotWet (f ss / N index i ent blk entx value room_num equipment_num typeid air_exhaust preserve_heat power surface_area surface_temp water_area water_temp)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "ROOM_NUM")
                (progn
                  (setq room_num (cdr (assoc 1 entx)))
                  (princ (strcat "\"room_num\": \"" room_num "\",") f)
                  (princ (strcat "\"block_data\": \"" "hotwet" "\",") f)
                )
              )
              (if (= value "EQUIPMENT_NUM")
                (progn
                  (setq equipment_num (cdr (assoc 1 entx)))
                  (princ (strcat "\"equipment_num\": \"" equipment_num "\",") f)
                )
              )
              (if (= value "TYPE")
                (progn
                  (setq typeid (cdr (assoc 1 entx)))
                  (princ (strcat "\"type\": \"" typeid "\",") f)
                )
              )
              (if (= value "AIR_EXHAUST")
                (progn
                  (setq air_exhaust (cdr (assoc 1 entx)))
                  (princ (strcat "\"air_exhaust\": \"" air_exhaust "\",") f)
                )
              )
              (if (= value "PRESERVE_HEAT")
                (progn
                  (setq preserve_heat (cdr (assoc 1 entx)))
                  (princ (strcat "\"preserve_heat\": \"" preserve_heat "\",") f)
                )
              )
              (if (= value "POWER")
                (progn
                  (setq power (cdr (assoc 1 entx)))
                  (princ (strcat "\"power\": \"" power "\",") f)
                )
              )
              (if (= value "SURFACE_AREA")
                (progn
                  (setq surface_area (cdr (assoc 1 entx)))
                  (princ (strcat "\"surface_area\": \"" surface_area "\",") f)
                )
              )
              (if (= value "SURFACE_TEMP")
                (progn
                  (setq surface_temp (cdr (assoc 1 entx)))
                  (princ (strcat "\"surface_temp\": \"" surface_temp "\",") f)
                )
              )
              (if (= value "WATER_AREA")
                (progn
                  (setq water_area (cdr (assoc 1 entx)))
                  (princ (strcat "\"water_area\": \"" water_area "\",") f)
                )
              )
              (if (= value "WATER_TEMP")
                (progn
                  (setq water_temp (cdr (assoc 1 entx)))
                  (princ (strcat "\"water_temp\": \"" water_temp "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form SubstanceData Block
(defun ExtactGlobalSubstance (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "ROOM_NUM")
                (progn
                  (setq room_num (cdr (assoc 1 entx)))
                  (princ (strcat "\"room_num\": \"" room_num "\",") f)
                  (princ (strcat "\"block_data\": \"" "substance" "\",") f)
                )
              )
              (if (= value "SUBSTANCE_NAME")
                (progn
                  (setq substance_name (cdr (assoc 1 entx)))
                  (princ (strcat "\"substance_name\": \"" substance_name "\",")
                   f)
                )
              )
              (if (= value "VALUE_NUM")
                (progn
                  (setq value_num (cdr (assoc 1 entx)))
                  (princ (strcat "\"value_num\": \"" value_num "\",") f)
                )
              )
              (if (= value "PUMPSEAL_NUM")
                (progn
                  (setq pumpseal_num (cdr (assoc 1 entx)))
                  (princ (strcat "\"pumpseal_num\": \"" pumpseal_num "\",") f)
                )
              )
              (if (= value "FLANGE_NUM")
                (progn
                  (setq flange_num (cdr (assoc 1 entx)))
                  (princ (strcat "\"flange_num\": \"" flange_num "\",") f)
                )
              )
              (if (= value "DISCHARGE_NUM")
                (progn
                  (setq discharge_num (cdr (assoc 1 entx)))
                  (princ (strcat "\"discharge_num\": \"" discharge_num "\",") f)
                )
              )
              (if (= value "SAFETY_NUM")
                (progn
                  (setq safety_num (cdr (assoc 1 entx)))
                  (princ (strcat "\"safety_num\": \"" safety_num "\",") f)
                )
              )
              (if (= value "COMPRESS_NUM")
                (progn
                  (setq compress_num (cdr (assoc 1 entx)))
                  (princ (strcat "\"compress_num\": \"" compress_num "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form RoomData Block
(defun ExtactGlobalRoom (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "ROOM_NUM")
                (progn
                  (setq room_num (cdr (assoc 1 entx)))
                  (princ (strcat "\"room_num\": \"" room_num "\",") f)
                  (princ (strcat "\"block_data\": \"" "room" "\",") f)
                )
              )
              (if (= value "ROOM_NAME")
                (progn
                  (setq room_name (cdr (assoc 1 entx)))
                  (princ (strcat "\"room_name\": \"" room_name "\",") f)
                )
              )
              (if (= value "ROOM_AREA")
                (progn
                  (setq room_area (cdr (assoc 1 entx)))
                  (princ (strcat "\"room_area\": \"" room_area "\",") f)
                )
              )
              (if (= value "ROOM_HEIGHT")
                (progn
                  (setq room_height (cdr (assoc 1 entx)))
                  (princ (strcat "\"room_height\": \"" room_height "\",") f)
                )
              )
              (if (= value "ROOM_PRESSURE")
                (progn
                  (setq room_pressure (cdr (assoc 1 entx)))
                  (princ (strcat "\"room_pressure\": \"" room_pressure "\",") f)
                )
              )
              (if (= value "SUMMER_TEMP")
                (progn
                  (setq summer_temp (cdr (assoc 1 entx)))
                  (princ (strcat "\"summer_temp\": \"" summer_temp "\",") f)
                )
              )
              (if (= value "SUMMER_REHUMIDITY")
                (progn
                  (setq summer_rehumidity (cdr (assoc 1 entx)))
                  (princ (strcat "\"summer_rehumidity\": \"" summer_rehumidity "\",") f)
                )
              )
              (if (= value "WINTER_TEMP")
                (progn
                  (setq winter_temp (cdr (assoc 1 entx)))
                  (princ (strcat "\"winter_temp\": \"" winter_temp "\",") f)
                )
              )
              (if (= value "WINTER_REHUMIDITY")
                (progn
                  (setq winter_rehumidity (cdr (assoc 1 entx)))
                  (princ (strcat "\"winter_rehumidity\": \"" winter_rehumidity "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form the for PipeArrow Blocks
(defun ExtactPipeArrow (f ss / N index i ent blk entx value pipenum substance temp pressure phase fromP toP insulation)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "PIPENUM")
                (progn
                  (setq pipenum (cdr (assoc 1 entx)))
                  (princ (strcat "\"pipenum\": \"" pipenum "\",") f)
                )
              )
              (if (= value "SUBSTANCE")
                (progn
                  (setq substance (cdr (assoc 1 entx)))
                  (princ (strcat "\"substance\": \"" substance "\",") f)
                )
              )
              (if (= value "TEMP")
                (progn
                  (setq temp (cdr (assoc 1 entx)))
                  (princ (strcat "\"temp\": \"" temp "\",") f)
                )
              )
              (if (= value "PRESSURE")
                (progn
                  (setq pressure (cdr (assoc 1 entx)))
                  (princ (strcat "\"pressure\": \"" pressure "\",") f)
                )
              )
              (if (= value "PHASE")
                (progn
                  (setq phase (cdr (assoc 1 entx)))
                  (princ (strcat "\"phase\": \"" phase "\",") f)
                )
              )
              (if (= value "FROM")
                (progn
                  (setq fromP (cdr (assoc 1 entx)))
                  (princ (strcat "\"from\": \"" fromP "\",") f)
                )
              )
              (if (= value "TO")
                (progn
                  (setq toP (cdr (assoc 1 entx)))
                  (princ (strcat "\"to\": \"" toP "\",") f)
                )
              )
              (if (= value "INSULATION")
                (progn
                  (setq insulation (cdr (assoc 1 entx)))
                  (princ (strcat "\"insulation\": \"" insulation "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)
