;冯大龙编于2020年
(princ "\n数据流一体化开发者：冯大龙、谢雨东")
(princ "\n工艺专业：暖通全面通风条件数据提取命令：nsglobal")
(princ "\n工艺专业：做「电气条件」数据提取命令：gselectric")
(princ "\n工艺专业：做「仪表条件」数据提取命令：gsinstrument")
(princ "\n工艺专业：做「外管条件」数据提取命令：gsouterpipe")
(princ "\n工艺专业：做「设备一览表」数据提取命令：gsequipment")
(princ "\n工艺专业：做「管道特性表」数据提取命令：gspipe")

; get the current file direction
(defun getFileDir (/ fn)
  (print "请输入拟输出的文件名（无需扩展名），输出文件自动存放在 CAD 文件同一个文件夹内")
  (setq fn (getstring "\nfilename: "))
  (setq currentDir (getvar "dwgprefix"))
  (setq fn (strcat currentDir fn ".txt"))
)

;  the command for extarcting data from the for PipeArrow Blocks
(defun c:gspipe (/ fn f ssLeft ssRight)
  (setq fn (getFileDir))
  (setq f (open fn "w"))
  (setq ssLeft (ssget "x" '((0 . "INSERT") (2 . "PipeArrowLeft"))))
  (setq ssRight (ssget "x" '((0 . "INSERT") (2 . "PipeArrowRight"))))
  (ExtactPipeArrow f ssLeft)
  (ExtactPipeArrow f ssRight)
  (close f)
  ; tansfor the encode
  (file-encode-trans fn "gb2312" "utf-8")
  (print "数据提取成功")(princ)
)

; the command for extarcting data from globalVentilation Block
(defun c:nsglobal (/ fn f)
  (setq fn (getFileDir))
  (setq f (open fn "w"))
  (setq ssRoom (ssget "x" '((0 . "INSERT") (2 . "RoomData"))))
  (setq ssSubstance (ssget "x" '((0 . "INSERT") (2 . "SubstanceData"))))
  (setq ssHotWet (ssget "x" '((0 . "INSERT") (2 . "HotWetData"))))
  (ExtactGlobalRoom f ssRoom)
  (ExtactGlobalSubstance f ssSubstance)
  (ExtactGlobalHotWet f ssHotWet)
  (close f)
  ; tansfor the encode
  (file-encode-trans fn "gb2312" "utf-8")
  (print "数据提取成功")(princ)
)

; extarct data form HotWetData Block
(defun ExtactGlobalHotWet (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "ROOM_NUM")
                (progn
                  (setq room_num (cdr (assoc 1 entx)))
                  (princ (strcat "\"room_num\": \"" room_num "\",") f)
                  (princ (strcat "\"block_data\": \"" "hotwet" "\",") f)
                )
              )
              (if (= value "EQUIPMENT_NUM")
                (progn
                  (setq equipment_num (cdr (assoc 1 entx)))
                  (princ (strcat "\"equipment_num\": \"" equipment_num "\",") f)
                )
              )
              (if (= value "TYPE")
                (progn
                  (setq typeid (cdr (assoc 1 entx)))
                  (princ (strcat "\"type\": \"" typeid "\",") f)
                )
              )
              (if (= value "AIR_EXHAUST")
                (progn
                  (setq air_exhaust (cdr (assoc 1 entx)))
                  (princ (strcat "\"air_exhaust\": \"" air_exhaust "\",") f)
                )
              )
              (if (= value "PRESERVE_HEAT")
                (progn
                  (setq preserve_heat (cdr (assoc 1 entx)))
                  (princ (strcat "\"preserve_heat\": \"" preserve_heat "\",") f)
                )
              )
              (if (= value "POWER")
                (progn
                  (setq power (cdr (assoc 1 entx)))
                  (princ (strcat "\"power\": \"" power "\",") f)
                )
              )
              (if (= value "SURFACE_AREA")
                (progn
                  (setq surface_area (cdr (assoc 1 entx)))
                  (princ (strcat "\"surface_area\": \"" surface_area "\",") f)
                )
              )
              (if (= value "SURFACE_TEMP")
                (progn
                  (setq surface_temp (cdr (assoc 1 entx)))
                  (princ (strcat "\"surface_temp\": \"" surface_temp "\",") f)
                )
              )
              (if (= value "WATER_AREA")
                (progn
                  (setq water_area (cdr (assoc 1 entx)))
                  (princ (strcat "\"water_area\": \"" water_area "\",") f)
                )
              )
              (if (= value "WATER_TEMP")
                (progn
                  (setq water_temp (cdr (assoc 1 entx)))
                  (princ (strcat "\"water_temp\": \"" water_temp "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form SubstanceData Block
(defun ExtactGlobalSubstance (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "ROOM_NUM")
                (progn
                  (setq room_num (cdr (assoc 1 entx)))
                  (princ (strcat "\"room_num\": \"" room_num "\",") f)
                  (princ (strcat "\"block_data\": \"" "substance" "\",") f)
                )
              )
              (if (= value "SUBSTANCE_NAME")
                (progn
                  (setq substance_name (cdr (assoc 1 entx)))
                  (princ (strcat "\"substance_name\": \"" substance_name "\",")
                   f)
                )
              )
              (if (= value "VALUE_NUM")
                (progn
                  (setq value_num (cdr (assoc 1 entx)))
                  (princ (strcat "\"value_num\": \"" value_num "\",") f)
                )
              )
              (if (= value "PUMPSEAL_NUM")
                (progn
                  (setq pumpseal_num (cdr (assoc 1 entx)))
                  (princ (strcat "\"pumpseal_num\": \"" pumpseal_num "\",") f)
                )
              )
              (if (= value "FLANGE_NUM")
                (progn
                  (setq flange_num (cdr (assoc 1 entx)))
                  (princ (strcat "\"flange_num\": \"" flange_num "\",") f)
                )
              )
              (if (= value "DISCHARGE_NUM")
                (progn
                  (setq discharge_num (cdr (assoc 1 entx)))
                  (princ (strcat "\"discharge_num\": \"" discharge_num "\",") f)
                )
              )
              (if (= value "SAFETY_NUM")
                (progn
                  (setq safety_num (cdr (assoc 1 entx)))
                  (princ (strcat "\"safety_num\": \"" safety_num "\",") f)
                )
              )
              (if (= value "COMPRESS_NUM")
                (progn
                  (setq compress_num (cdr (assoc 1 entx)))
                  (princ (strcat "\"compress_num\": \"" compress_num "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form RoomData Block
(defun ExtactGlobalRoom (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "ROOM_NUM")
                (progn
                  (setq room_num (cdr (assoc 1 entx)))
                  (princ (strcat "\"room_num\": \"" room_num "\",") f)
                  (princ (strcat "\"block_data\": \"" "room" "\",") f)
                )
              )
              (if (= value "ROOM_NAME")
                (progn
                  (setq room_name (cdr (assoc 1 entx)))
                  (princ (strcat "\"room_name\": \"" room_name "\",") f)
                )
              )
              (if (= value "ROOM_AREA")
                (progn
                  (setq room_area (cdr (assoc 1 entx)))
                  (princ (strcat "\"room_area\": \"" room_area "\",") f)
                )
              )
              (if (= value "ROOM_HEIGHT")
                (progn
                  (setq room_height (cdr (assoc 1 entx)))
                  (princ (strcat "\"room_height\": \"" room_height "\",") f)
                )
              )
              (if (= value "ROOM_PRESSURE")
                (progn
                  (setq room_pressure (cdr (assoc 1 entx)))
                  (princ (strcat "\"room_pressure\": \"" room_pressure "\",") f)
                )
              )
              (if (= value "SUMMER_TEMP")
                (progn
                  (setq summer_temp (cdr (assoc 1 entx)))
                  (princ (strcat "\"summer_temp\": \"" summer_temp "\",") f)
                )
              )
              (if (= value "SUMMER_REHUMIDITY")
                (progn
                  (setq summer_rehumidity (cdr (assoc 1 entx)))
                  (princ (strcat "\"summer_rehumidity\": \"" summer_rehumidity "\",") f)
                )
              )
              (if (= value "WINTER_TEMP")
                (progn
                  (setq winter_temp (cdr (assoc 1 entx)))
                  (princ (strcat "\"winter_temp\": \"" winter_temp "\",") f)
                )
              )
              (if (= value "WINTER_REHUMIDITY")
                (progn
                  (setq winter_rehumidity (cdr (assoc 1 entx)))
                  (princ (strcat "\"winter_rehumidity\": \"" winter_rehumidity "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; extarct data form the for PipeArrow Blocks
(defun ExtactPipeArrow (f ss / N index i ent blk entx value pipenum substance temp pressure phase fromP toP insulation)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (if (= value "PIPENUM")
                (progn
                  (setq pipenum (cdr (assoc 1 entx)))
                  (princ (strcat "\"pipenum\": \"" pipenum "\",") f)
                )
              )
              (if (= value "SUBSTANCE")
                (progn
                  (setq substance (cdr (assoc 1 entx)))
                  (princ (strcat "\"substance\": \"" substance "\",") f)
                )
              )
              (if (= value "TEMP")
                (progn
                  (setq temp (cdr (assoc 1 entx)))
                  (princ (strcat "\"temp\": \"" temp "\",") f)
                )
              )
              (if (= value "PRESSURE")
                (progn
                  (setq pressure (cdr (assoc 1 entx)))
                  (princ (strcat "\"pressure\": \"" pressure "\",") f)
                )
              )
              (if (= value "PHASE")
                (progn
                  (setq phase (cdr (assoc 1 entx)))
                  (princ (strcat "\"phase\": \"" phase "\",") f)
                )
              )
              (if (= value "FROM")
                (progn
                  (setq fromP (cdr (assoc 1 entx)))
                  (princ (strcat "\"from\": \"" fromP "\",") f)
                )
              )
              (if (= value "TO")
                (progn
                  (setq toP (cdr (assoc 1 entx)))
                  (princ (strcat "\"to\": \"" toP "\",") f)
                )
              )
              (if (= value "INSULATION")
                (progn
                  (setq insulation (cdr (assoc 1 entx)))
                  (princ (strcat "\"insulation\": \"" insulation "\"") f)
                )
              )
              ; ?????????,???????
              (setq entx (entget (entnext (cdr (assoc -1 entx)))))
            )
            (princ "}\n" f)
            (entupd blk)
            (setq i (+ 1 i))
          )
        )
        (setq index (+ 1 index))
        (princ)
      )
    )
  )
)

; tansfor gb2312 to utf8
(defun file-encode-trans (file charset1 charset2 / obj encode)
  (setq obj (vlax-create-object "ADODB.Stream"))
  (vlax-put-property obj 'type 2);1????? 2?????
  (vlax-put-property obj 'mode 3);1-?,2-?,3-??
  (vlax-invoke obj 'open)
  (vlax-put-property obj "charset" charset1);;unicode;utf-8;ascii;gb2312;big5;gbk
  (vlax-invoke-method obj 'loadfromfile file)
  (setq encode (vlax-invoke obj 'readtext))
  (vlax-invoke obj 'close)
  (vlax-release-object obj)
  (setq obj (vlax-create-object "ADODB.Stream"))
  (vlax-put-property obj 'type 2);1????? 2?????
  (vlax-put-property obj 'mode 3);1-?,2-?,3-??
  (vlax-invoke obj 'open)
  (vlax-put-property obj "charset" charset2);;unicode;utf-8;ascii;gb2312;big5;gbk
  (vlax-invoke obj 'writetext encode)
  (vlax-invoke-method obj 'savetofile file 2);1??,2??
  (vlax-invoke obj 'flush);???????????
  (vlax-invoke obj 'close)
  (vlax-release-object obj)
)
